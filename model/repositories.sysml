package Repositories {
    doc /* Generated by model.py from repos.yaml; the facts are imported at run time (sense.py). */
    private import Governance::*;

    part 'Open-MBEE/flexo-change-adapter' : Repository {
        attribute :>> type = Type::tool;
        attribute :>> stage = Stage::graduated;
        attribute :>> attestedEndOfSupportNote = false;
        attribute :>> attestedContributingContent = true;
        attribute :>> attestedDependencyPolicy = true;
        attribute :>> attestedServicePins = true;
        attribute :>> attestedSignedWithProvenance = true;
        attribute :>> attestedNoBuiltExecutables = true;
        attribute :>> attestedDesignCurrent = true;
        attribute :>> attestedDisclosureFollowed = true;
        attribute :>> attestedStableReleasePolicy = false;
        attribute :>> attestedCoordinatedReleases = true;
        attribute :>> attestedWorkflowsHardened = true;
    }
    satisfy requirement 'Open-MBEE/flexo-change-adapter: archived' : Policies::ArchiveNotice::Archived by 'Open-MBEE/flexo-change-adapter';
    satisfy requirement 'Open-MBEE/flexo-change-adapter: end-of-support-note' : Policies::ArchiveNotice::EndOfSupportNote by 'Open-MBEE/flexo-change-adapter';
    satisfy requirement 'Open-MBEE/flexo-change-adapter: review-required' : Policies::ChangeReview::ReviewRequired by 'Open-MBEE/flexo-change-adapter';
    satisfy requirement 'Open-MBEE/flexo-change-adapter: checks-required' : Policies::ChangeReview::ChecksRequired by 'Open-MBEE/flexo-change-adapter';
    satisfy requirement 'Open-MBEE/flexo-change-adapter: codeowners-present' : Policies::Codeowners::CodeownersPresent by 'Open-MBEE/flexo-change-adapter';
    satisfy requirement 'Open-MBEE/flexo-change-adapter: codeowners-valid' : Policies::Codeowners::CodeownersValid by 'Open-MBEE/flexo-change-adapter';
    satisfy requirement 'Open-MBEE/flexo-change-adapter: contributing-present' : Policies::Contributing::ContributingPresent by 'Open-MBEE/flexo-change-adapter';
    satisfy requirement 'Open-MBEE/flexo-change-adapter: contributing-content' : Policies::Contributing::ContributingContent by 'Open-MBEE/flexo-change-adapter';
    satisfy requirement 'Open-MBEE/flexo-change-adapter: dependabot-alerts-on' : Policies::DependencyManagement::DependabotAlertsOn by 'Open-MBEE/flexo-change-adapter';
    satisfy requirement 'Open-MBEE/flexo-change-adapter: dependency-policy' : Policies::DependencyManagement::DependencyPolicy by 'Open-MBEE/flexo-change-adapter';
    satisfy requirement 'Open-MBEE/flexo-change-adapter: service-pins' : Policies::DependencyManagement::ServicePins by 'Open-MBEE/flexo-change-adapter';
    satisfy requirement 'Open-MBEE/flexo-change-adapter: no-force-push' : Policies::HistoryProtection::NoForcePush by 'Open-MBEE/flexo-change-adapter';
    satisfy requirement 'Open-MBEE/flexo-change-adapter: no-deletion' : Policies::HistoryProtection::NoDeletion by 'Open-MBEE/flexo-change-adapter';
    satisfy requirement 'Open-MBEE/flexo-change-adapter: license-allowed' : Policies::LicenseByType::LicenseAllowed by 'Open-MBEE/flexo-change-adapter';
    satisfy requirement 'Open-MBEE/flexo-change-adapter: readme-present' : Policies::ProjectFiles::ReadmePresent by 'Open-MBEE/flexo-change-adapter';
    satisfy requirement 'Open-MBEE/flexo-change-adapter: sbom-attached' : Policies::ReleaseIntegrity::SbomAttached by 'Open-MBEE/flexo-change-adapter';
    satisfy requirement 'Open-MBEE/flexo-change-adapter: release-immutable' : Policies::ReleaseIntegrity::ReleaseImmutable by 'Open-MBEE/flexo-change-adapter';
    satisfy requirement 'Open-MBEE/flexo-change-adapter: signed-with-provenance' : Policies::ReleaseIntegrity::SignedWithProvenance by 'Open-MBEE/flexo-change-adapter';
    satisfy requirement 'Open-MBEE/flexo-change-adapter: no-built-executables' : Policies::ReleaseIntegrity::NoBuiltExecutables by 'Open-MBEE/flexo-change-adapter';
    satisfy requirement 'Open-MBEE/flexo-change-adapter: push-protection-on' : Policies::SecretProtection::PushProtectionOn by 'Open-MBEE/flexo-change-adapter';
    satisfy requirement 'Open-MBEE/flexo-change-adapter: design-current' : Policies::SecurityDesign::DesignCurrent by 'Open-MBEE/flexo-change-adapter';
    satisfy requirement 'Open-MBEE/flexo-change-adapter: security-policy-present' : Policies::SecurityPolicy::SecurityPolicyPresent by 'Open-MBEE/flexo-change-adapter';
    satisfy requirement 'Open-MBEE/flexo-change-adapter: private-reporting-on' : Policies::SecurityPolicy::PrivateReportingOn by 'Open-MBEE/flexo-change-adapter';
    satisfy requirement 'Open-MBEE/flexo-change-adapter: disclosure-followed' : Policies::SecurityPolicy::DisclosureFollowed by 'Open-MBEE/flexo-change-adapter';
    satisfy requirement 'Open-MBEE/flexo-change-adapter: semver-tags' : Policies::SemanticVersioning::SemverTags by 'Open-MBEE/flexo-change-adapter';
    satisfy requirement 'Open-MBEE/flexo-change-adapter: stable-release-policy' : Policies::SemanticVersioning::StableReleasePolicy by 'Open-MBEE/flexo-change-adapter';
    satisfy requirement 'Open-MBEE/flexo-change-adapter: code-scanning-configured' : Policies::StaticAnalysis::CodeScanningConfigured by 'Open-MBEE/flexo-change-adapter';
    satisfy requirement 'Open-MBEE/flexo-change-adapter: no-open-critical' : Policies::StaticAnalysis::NoOpenCritical by 'Open-MBEE/flexo-change-adapter';
    satisfy requirement 'Open-MBEE/flexo-change-adapter: verified-owners' : Policies::VerifiedCodeOwners::VerifiedOwners by 'Open-MBEE/flexo-change-adapter';
    satisfy requirement 'Open-MBEE/flexo-change-adapter: dependency-alerts-on-time' : Policies::VulnerabilityRemediation::DependencyAlertsOnTime by 'Open-MBEE/flexo-change-adapter';
    satisfy requirement 'Open-MBEE/flexo-change-adapter: scanning-clean' : Policies::VulnerabilityRemediation::ScanningClean by 'Open-MBEE/flexo-change-adapter';
    satisfy requirement 'Open-MBEE/flexo-change-adapter: coordinated-releases' : Policies::VulnerabilityRemediation::CoordinatedReleases by 'Open-MBEE/flexo-change-adapter';
    satisfy requirement 'Open-MBEE/flexo-change-adapter: default-token-read' : Policies::WorkflowLeastPrivilege::DefaultTokenRead by 'Open-MBEE/flexo-change-adapter';
    satisfy requirement 'Open-MBEE/flexo-change-adapter: workflows-hardened' : Policies::WorkflowLeastPrivilege::WorkflowsHardened by 'Open-MBEE/flexo-change-adapter';

    part 'Open-MBEE/OpenSysML' : Repository {
        attribute :>> type = Type::tool;
        attribute :>> stage = Stage::graduated;
        attribute :>> attestedEndOfSupportNote = false;
        attribute :>> attestedContributingContent = true;
        attribute :>> attestedDependencyPolicy = false;
        attribute :>> attestedServicePins = false;
        attribute :>> attestedSignedWithProvenance = true;
        attribute :>> attestedNoBuiltExecutables = false;
        attribute :>> attestedDesignCurrent = false;
        attribute :>> attestedDisclosureFollowed = true;
        attribute :>> attestedStableReleasePolicy = false;
        attribute :>> attestedCoordinatedReleases = true;
        attribute :>> attestedWorkflowsHardened = false;
    }
    satisfy requirement 'Open-MBEE/OpenSysML: archived' : Policies::ArchiveNotice::Archived by 'Open-MBEE/OpenSysML';
    satisfy requirement 'Open-MBEE/OpenSysML: end-of-support-note' : Policies::ArchiveNotice::EndOfSupportNote by 'Open-MBEE/OpenSysML';
    satisfy requirement 'Open-MBEE/OpenSysML: review-required' : Policies::ChangeReview::ReviewRequired by 'Open-MBEE/OpenSysML';
    satisfy requirement 'Open-MBEE/OpenSysML: checks-required' : Policies::ChangeReview::ChecksRequired by 'Open-MBEE/OpenSysML';
    satisfy requirement 'Open-MBEE/OpenSysML: codeowners-present' : Policies::Codeowners::CodeownersPresent by 'Open-MBEE/OpenSysML';
    satisfy requirement 'Open-MBEE/OpenSysML: codeowners-valid' : Policies::Codeowners::CodeownersValid by 'Open-MBEE/OpenSysML';
    satisfy requirement 'Open-MBEE/OpenSysML: contributing-present' : Policies::Contributing::ContributingPresent by 'Open-MBEE/OpenSysML';
    satisfy requirement 'Open-MBEE/OpenSysML: contributing-content' : Policies::Contributing::ContributingContent by 'Open-MBEE/OpenSysML';
    satisfy requirement 'Open-MBEE/OpenSysML: dependabot-alerts-on' : Policies::DependencyManagement::DependabotAlertsOn by 'Open-MBEE/OpenSysML';
    satisfy requirement 'Open-MBEE/OpenSysML: dependency-policy' : Policies::DependencyManagement::DependencyPolicy by 'Open-MBEE/OpenSysML';
    satisfy requirement 'Open-MBEE/OpenSysML: service-pins' : Policies::DependencyManagement::ServicePins by 'Open-MBEE/OpenSysML';
    satisfy requirement 'Open-MBEE/OpenSysML: no-force-push' : Policies::HistoryProtection::NoForcePush by 'Open-MBEE/OpenSysML';
    satisfy requirement 'Open-MBEE/OpenSysML: no-deletion' : Policies::HistoryProtection::NoDeletion by 'Open-MBEE/OpenSysML';
    satisfy requirement 'Open-MBEE/OpenSysML: license-allowed' : Policies::LicenseByType::LicenseAllowed by 'Open-MBEE/OpenSysML';
    satisfy requirement 'Open-MBEE/OpenSysML: readme-present' : Policies::ProjectFiles::ReadmePresent by 'Open-MBEE/OpenSysML';
    satisfy requirement 'Open-MBEE/OpenSysML: sbom-attached' : Policies::ReleaseIntegrity::SbomAttached by 'Open-MBEE/OpenSysML';
    satisfy requirement 'Open-MBEE/OpenSysML: release-immutable' : Policies::ReleaseIntegrity::ReleaseImmutable by 'Open-MBEE/OpenSysML';
    satisfy requirement 'Open-MBEE/OpenSysML: signed-with-provenance' : Policies::ReleaseIntegrity::SignedWithProvenance by 'Open-MBEE/OpenSysML';
    satisfy requirement 'Open-MBEE/OpenSysML: no-built-executables' : Policies::ReleaseIntegrity::NoBuiltExecutables by 'Open-MBEE/OpenSysML';
    satisfy requirement 'Open-MBEE/OpenSysML: push-protection-on' : Policies::SecretProtection::PushProtectionOn by 'Open-MBEE/OpenSysML';
    satisfy requirement 'Open-MBEE/OpenSysML: design-current' : Policies::SecurityDesign::DesignCurrent by 'Open-MBEE/OpenSysML';
    satisfy requirement 'Open-MBEE/OpenSysML: security-policy-present' : Policies::SecurityPolicy::SecurityPolicyPresent by 'Open-MBEE/OpenSysML';
    satisfy requirement 'Open-MBEE/OpenSysML: private-reporting-on' : Policies::SecurityPolicy::PrivateReportingOn by 'Open-MBEE/OpenSysML';
    satisfy requirement 'Open-MBEE/OpenSysML: disclosure-followed' : Policies::SecurityPolicy::DisclosureFollowed by 'Open-MBEE/OpenSysML';
    satisfy requirement 'Open-MBEE/OpenSysML: semver-tags' : Policies::SemanticVersioning::SemverTags by 'Open-MBEE/OpenSysML';
    satisfy requirement 'Open-MBEE/OpenSysML: stable-release-policy' : Policies::SemanticVersioning::StableReleasePolicy by 'Open-MBEE/OpenSysML';
    satisfy requirement 'Open-MBEE/OpenSysML: code-scanning-configured' : Policies::StaticAnalysis::CodeScanningConfigured by 'Open-MBEE/OpenSysML';
    satisfy requirement 'Open-MBEE/OpenSysML: no-open-critical' : Policies::StaticAnalysis::NoOpenCritical by 'Open-MBEE/OpenSysML';
    satisfy requirement 'Open-MBEE/OpenSysML: verified-owners' : Policies::VerifiedCodeOwners::VerifiedOwners by 'Open-MBEE/OpenSysML';
    satisfy requirement 'Open-MBEE/OpenSysML: dependency-alerts-on-time' : Policies::VulnerabilityRemediation::DependencyAlertsOnTime by 'Open-MBEE/OpenSysML';
    satisfy requirement 'Open-MBEE/OpenSysML: scanning-clean' : Policies::VulnerabilityRemediation::ScanningClean by 'Open-MBEE/OpenSysML';
    satisfy requirement 'Open-MBEE/OpenSysML: coordinated-releases' : Policies::VulnerabilityRemediation::CoordinatedReleases by 'Open-MBEE/OpenSysML';
    satisfy requirement 'Open-MBEE/OpenSysML: default-token-read' : Policies::WorkflowLeastPrivilege::DefaultTokenRead by 'Open-MBEE/OpenSysML';
    satisfy requirement 'Open-MBEE/OpenSysML: workflows-hardened' : Policies::WorkflowLeastPrivilege::WorkflowsHardened by 'Open-MBEE/OpenSysML';

    part 'Open-MBEE/OpenSysML-Extensions-Library' : Repository {
        attribute :>> type = Type::tool;
        attribute :>> stage = Stage::incubating;
        attribute :>> attestedEndOfSupportNote = false;
        attribute :>> attestedContributingContent = false;
        attribute :>> attestedDependencyPolicy = false;
        attribute :>> attestedServicePins = false;
        attribute :>> attestedSignedWithProvenance = false;
        attribute :>> attestedNoBuiltExecutables = false;
        attribute :>> attestedDesignCurrent = false;
        attribute :>> attestedDisclosureFollowed = false;
        attribute :>> attestedStableReleasePolicy = false;
        attribute :>> attestedCoordinatedReleases = false;
        attribute :>> attestedWorkflowsHardened = false;
    }
    satisfy requirement 'Open-MBEE/OpenSysML-Extensions-Library: archived' : Policies::ArchiveNotice::Archived by 'Open-MBEE/OpenSysML-Extensions-Library';
    satisfy requirement 'Open-MBEE/OpenSysML-Extensions-Library: end-of-support-note' : Policies::ArchiveNotice::EndOfSupportNote by 'Open-MBEE/OpenSysML-Extensions-Library';
    satisfy requirement 'Open-MBEE/OpenSysML-Extensions-Library: review-required' : Policies::ChangeReview::ReviewRequired by 'Open-MBEE/OpenSysML-Extensions-Library';
    satisfy requirement 'Open-MBEE/OpenSysML-Extensions-Library: checks-required' : Policies::ChangeReview::ChecksRequired by 'Open-MBEE/OpenSysML-Extensions-Library';
    satisfy requirement 'Open-MBEE/OpenSysML-Extensions-Library: codeowners-present' : Policies::Codeowners::CodeownersPresent by 'Open-MBEE/OpenSysML-Extensions-Library';
    satisfy requirement 'Open-MBEE/OpenSysML-Extensions-Library: codeowners-valid' : Policies::Codeowners::CodeownersValid by 'Open-MBEE/OpenSysML-Extensions-Library';
    satisfy requirement 'Open-MBEE/OpenSysML-Extensions-Library: contributing-present' : Policies::Contributing::ContributingPresent by 'Open-MBEE/OpenSysML-Extensions-Library';
    satisfy requirement 'Open-MBEE/OpenSysML-Extensions-Library: contributing-content' : Policies::Contributing::ContributingContent by 'Open-MBEE/OpenSysML-Extensions-Library';
    satisfy requirement 'Open-MBEE/OpenSysML-Extensions-Library: dependabot-alerts-on' : Policies::DependencyManagement::DependabotAlertsOn by 'Open-MBEE/OpenSysML-Extensions-Library';
    satisfy requirement 'Open-MBEE/OpenSysML-Extensions-Library: dependency-policy' : Policies::DependencyManagement::DependencyPolicy by 'Open-MBEE/OpenSysML-Extensions-Library';
    satisfy requirement 'Open-MBEE/OpenSysML-Extensions-Library: service-pins' : Policies::DependencyManagement::ServicePins by 'Open-MBEE/OpenSysML-Extensions-Library';
    satisfy requirement 'Open-MBEE/OpenSysML-Extensions-Library: no-force-push' : Policies::HistoryProtection::NoForcePush by 'Open-MBEE/OpenSysML-Extensions-Library';
    satisfy requirement 'Open-MBEE/OpenSysML-Extensions-Library: no-deletion' : Policies::HistoryProtection::NoDeletion by 'Open-MBEE/OpenSysML-Extensions-Library';
    satisfy requirement 'Open-MBEE/OpenSysML-Extensions-Library: license-allowed' : Policies::LicenseByType::LicenseAllowed by 'Open-MBEE/OpenSysML-Extensions-Library';
    satisfy requirement 'Open-MBEE/OpenSysML-Extensions-Library: readme-present' : Policies::ProjectFiles::ReadmePresent by 'Open-MBEE/OpenSysML-Extensions-Library';
    satisfy requirement 'Open-MBEE/OpenSysML-Extensions-Library: sbom-attached' : Policies::ReleaseIntegrity::SbomAttached by 'Open-MBEE/OpenSysML-Extensions-Library';
    satisfy requirement 'Open-MBEE/OpenSysML-Extensions-Library: release-immutable' : Policies::ReleaseIntegrity::ReleaseImmutable by 'Open-MBEE/OpenSysML-Extensions-Library';
    satisfy requirement 'Open-MBEE/OpenSysML-Extensions-Library: signed-with-provenance' : Policies::ReleaseIntegrity::SignedWithProvenance by 'Open-MBEE/OpenSysML-Extensions-Library';
    satisfy requirement 'Open-MBEE/OpenSysML-Extensions-Library: no-built-executables' : Policies::ReleaseIntegrity::NoBuiltExecutables by 'Open-MBEE/OpenSysML-Extensions-Library';
    satisfy requirement 'Open-MBEE/OpenSysML-Extensions-Library: push-protection-on' : Policies::SecretProtection::PushProtectionOn by 'Open-MBEE/OpenSysML-Extensions-Library';
    satisfy requirement 'Open-MBEE/OpenSysML-Extensions-Library: design-current' : Policies::SecurityDesign::DesignCurrent by 'Open-MBEE/OpenSysML-Extensions-Library';
    satisfy requirement 'Open-MBEE/OpenSysML-Extensions-Library: security-policy-present' : Policies::SecurityPolicy::SecurityPolicyPresent by 'Open-MBEE/OpenSysML-Extensions-Library';
    satisfy requirement 'Open-MBEE/OpenSysML-Extensions-Library: private-reporting-on' : Policies::SecurityPolicy::PrivateReportingOn by 'Open-MBEE/OpenSysML-Extensions-Library';
    satisfy requirement 'Open-MBEE/OpenSysML-Extensions-Library: disclosure-followed' : Policies::SecurityPolicy::DisclosureFollowed by 'Open-MBEE/OpenSysML-Extensions-Library';
    satisfy requirement 'Open-MBEE/OpenSysML-Extensions-Library: semver-tags' : Policies::SemanticVersioning::SemverTags by 'Open-MBEE/OpenSysML-Extensions-Library';
    satisfy requirement 'Open-MBEE/OpenSysML-Extensions-Library: stable-release-policy' : Policies::SemanticVersioning::StableReleasePolicy by 'Open-MBEE/OpenSysML-Extensions-Library';
    satisfy requirement 'Open-MBEE/OpenSysML-Extensions-Library: code-scanning-configured' : Policies::StaticAnalysis::CodeScanningConfigured by 'Open-MBEE/OpenSysML-Extensions-Library';
    satisfy requirement 'Open-MBEE/OpenSysML-Extensions-Library: no-open-critical' : Policies::StaticAnalysis::NoOpenCritical by 'Open-MBEE/OpenSysML-Extensions-Library';
    satisfy requirement 'Open-MBEE/OpenSysML-Extensions-Library: verified-owners' : Policies::VerifiedCodeOwners::VerifiedOwners by 'Open-MBEE/OpenSysML-Extensions-Library';
    satisfy requirement 'Open-MBEE/OpenSysML-Extensions-Library: dependency-alerts-on-time' : Policies::VulnerabilityRemediation::DependencyAlertsOnTime by 'Open-MBEE/OpenSysML-Extensions-Library';
    satisfy requirement 'Open-MBEE/OpenSysML-Extensions-Library: scanning-clean' : Policies::VulnerabilityRemediation::ScanningClean by 'Open-MBEE/OpenSysML-Extensions-Library';
    satisfy requirement 'Open-MBEE/OpenSysML-Extensions-Library: coordinated-releases' : Policies::VulnerabilityRemediation::CoordinatedReleases by 'Open-MBEE/OpenSysML-Extensions-Library';
    satisfy requirement 'Open-MBEE/OpenSysML-Extensions-Library: default-token-read' : Policies::WorkflowLeastPrivilege::DefaultTokenRead by 'Open-MBEE/OpenSysML-Extensions-Library';
    satisfy requirement 'Open-MBEE/OpenSysML-Extensions-Library: workflows-hardened' : Policies::WorkflowLeastPrivilege::WorkflowsHardened by 'Open-MBEE/OpenSysML-Extensions-Library';

    part 'Open-MBEE/OpenSysML-REDK-Skills' : Repository {
        attribute :>> type = Type::tool;
        attribute :>> stage = Stage::sandbox;
        attribute :>> attestedEndOfSupportNote = false;
        attribute :>> attestedContributingContent = false;
        attribute :>> attestedDependencyPolicy = false;
        attribute :>> attestedServicePins = false;
        attribute :>> attestedSignedWithProvenance = false;
        attribute :>> attestedNoBuiltExecutables = false;
        attribute :>> attestedDesignCurrent = false;
        attribute :>> attestedDisclosureFollowed = false;
        attribute :>> attestedStableReleasePolicy = false;
        attribute :>> attestedCoordinatedReleases = false;
        attribute :>> attestedWorkflowsHardened = false;
    }
    satisfy requirement 'Open-MBEE/OpenSysML-REDK-Skills: archived' : Policies::ArchiveNotice::Archived by 'Open-MBEE/OpenSysML-REDK-Skills';
    satisfy requirement 'Open-MBEE/OpenSysML-REDK-Skills: end-of-support-note' : Policies::ArchiveNotice::EndOfSupportNote by 'Open-MBEE/OpenSysML-REDK-Skills';
    satisfy requirement 'Open-MBEE/OpenSysML-REDK-Skills: review-required' : Policies::ChangeReview::ReviewRequired by 'Open-MBEE/OpenSysML-REDK-Skills';
    satisfy requirement 'Open-MBEE/OpenSysML-REDK-Skills: checks-required' : Policies::ChangeReview::ChecksRequired by 'Open-MBEE/OpenSysML-REDK-Skills';
    satisfy requirement 'Open-MBEE/OpenSysML-REDK-Skills: codeowners-present' : Policies::Codeowners::CodeownersPresent by 'Open-MBEE/OpenSysML-REDK-Skills';
    satisfy requirement 'Open-MBEE/OpenSysML-REDK-Skills: codeowners-valid' : Policies::Codeowners::CodeownersValid by 'Open-MBEE/OpenSysML-REDK-Skills';
    satisfy requirement 'Open-MBEE/OpenSysML-REDK-Skills: contributing-present' : Policies::Contributing::ContributingPresent by 'Open-MBEE/OpenSysML-REDK-Skills';
    satisfy requirement 'Open-MBEE/OpenSysML-REDK-Skills: contributing-content' : Policies::Contributing::ContributingContent by 'Open-MBEE/OpenSysML-REDK-Skills';
    satisfy requirement 'Open-MBEE/OpenSysML-REDK-Skills: dependabot-alerts-on' : Policies::DependencyManagement::DependabotAlertsOn by 'Open-MBEE/OpenSysML-REDK-Skills';
    satisfy requirement 'Open-MBEE/OpenSysML-REDK-Skills: dependency-policy' : Policies::DependencyManagement::DependencyPolicy by 'Open-MBEE/OpenSysML-REDK-Skills';
    satisfy requirement 'Open-MBEE/OpenSysML-REDK-Skills: service-pins' : Policies::DependencyManagement::ServicePins by 'Open-MBEE/OpenSysML-REDK-Skills';
    satisfy requirement 'Open-MBEE/OpenSysML-REDK-Skills: no-force-push' : Policies::HistoryProtection::NoForcePush by 'Open-MBEE/OpenSysML-REDK-Skills';
    satisfy requirement 'Open-MBEE/OpenSysML-REDK-Skills: no-deletion' : Policies::HistoryProtection::NoDeletion by 'Open-MBEE/OpenSysML-REDK-Skills';
    satisfy requirement 'Open-MBEE/OpenSysML-REDK-Skills: license-allowed' : Policies::LicenseByType::LicenseAllowed by 'Open-MBEE/OpenSysML-REDK-Skills';
    satisfy requirement 'Open-MBEE/OpenSysML-REDK-Skills: readme-present' : Policies::ProjectFiles::ReadmePresent by 'Open-MBEE/OpenSysML-REDK-Skills';
    satisfy requirement 'Open-MBEE/OpenSysML-REDK-Skills: sbom-attached' : Policies::ReleaseIntegrity::SbomAttached by 'Open-MBEE/OpenSysML-REDK-Skills';
    satisfy requirement 'Open-MBEE/OpenSysML-REDK-Skills: release-immutable' : Policies::ReleaseIntegrity::ReleaseImmutable by 'Open-MBEE/OpenSysML-REDK-Skills';
    satisfy requirement 'Open-MBEE/OpenSysML-REDK-Skills: signed-with-provenance' : Policies::ReleaseIntegrity::SignedWithProvenance by 'Open-MBEE/OpenSysML-REDK-Skills';
    satisfy requirement 'Open-MBEE/OpenSysML-REDK-Skills: no-built-executables' : Policies::ReleaseIntegrity::NoBuiltExecutables by 'Open-MBEE/OpenSysML-REDK-Skills';
    satisfy requirement 'Open-MBEE/OpenSysML-REDK-Skills: push-protection-on' : Policies::SecretProtection::PushProtectionOn by 'Open-MBEE/OpenSysML-REDK-Skills';
    satisfy requirement 'Open-MBEE/OpenSysML-REDK-Skills: design-current' : Policies::SecurityDesign::DesignCurrent by 'Open-MBEE/OpenSysML-REDK-Skills';
    satisfy requirement 'Open-MBEE/OpenSysML-REDK-Skills: security-policy-present' : Policies::SecurityPolicy::SecurityPolicyPresent by 'Open-MBEE/OpenSysML-REDK-Skills';
    satisfy requirement 'Open-MBEE/OpenSysML-REDK-Skills: private-reporting-on' : Policies::SecurityPolicy::PrivateReportingOn by 'Open-MBEE/OpenSysML-REDK-Skills';
    satisfy requirement 'Open-MBEE/OpenSysML-REDK-Skills: disclosure-followed' : Policies::SecurityPolicy::DisclosureFollowed by 'Open-MBEE/OpenSysML-REDK-Skills';
    satisfy requirement 'Open-MBEE/OpenSysML-REDK-Skills: semver-tags' : Policies::SemanticVersioning::SemverTags by 'Open-MBEE/OpenSysML-REDK-Skills';
    satisfy requirement 'Open-MBEE/OpenSysML-REDK-Skills: stable-release-policy' : Policies::SemanticVersioning::StableReleasePolicy by 'Open-MBEE/OpenSysML-REDK-Skills';
    satisfy requirement 'Open-MBEE/OpenSysML-REDK-Skills: code-scanning-configured' : Policies::StaticAnalysis::CodeScanningConfigured by 'Open-MBEE/OpenSysML-REDK-Skills';
    satisfy requirement 'Open-MBEE/OpenSysML-REDK-Skills: no-open-critical' : Policies::StaticAnalysis::NoOpenCritical by 'Open-MBEE/OpenSysML-REDK-Skills';
    satisfy requirement 'Open-MBEE/OpenSysML-REDK-Skills: verified-owners' : Policies::VerifiedCodeOwners::VerifiedOwners by 'Open-MBEE/OpenSysML-REDK-Skills';
    satisfy requirement 'Open-MBEE/OpenSysML-REDK-Skills: dependency-alerts-on-time' : Policies::VulnerabilityRemediation::DependencyAlertsOnTime by 'Open-MBEE/OpenSysML-REDK-Skills';
    satisfy requirement 'Open-MBEE/OpenSysML-REDK-Skills: scanning-clean' : Policies::VulnerabilityRemediation::ScanningClean by 'Open-MBEE/OpenSysML-REDK-Skills';
    satisfy requirement 'Open-MBEE/OpenSysML-REDK-Skills: coordinated-releases' : Policies::VulnerabilityRemediation::CoordinatedReleases by 'Open-MBEE/OpenSysML-REDK-Skills';
    satisfy requirement 'Open-MBEE/OpenSysML-REDK-Skills: default-token-read' : Policies::WorkflowLeastPrivilege::DefaultTokenRead by 'Open-MBEE/OpenSysML-REDK-Skills';
    satisfy requirement 'Open-MBEE/OpenSysML-REDK-Skills: workflows-hardened' : Policies::WorkflowLeastPrivilege::WorkflowsHardened by 'Open-MBEE/OpenSysML-REDK-Skills';

    part 'Open-MBEE/airflow-provider-opensysml' : Repository {
        attribute :>> type = Type::tool;
        attribute :>> stage = Stage::sandbox;
        attribute :>> attestedEndOfSupportNote = false;
        attribute :>> attestedContributingContent = false;
        attribute :>> attestedDependencyPolicy = false;
        attribute :>> attestedServicePins = false;
        attribute :>> attestedSignedWithProvenance = false;
        attribute :>> attestedNoBuiltExecutables = false;
        attribute :>> attestedDesignCurrent = false;
        attribute :>> attestedDisclosureFollowed = false;
        attribute :>> attestedStableReleasePolicy = false;
        attribute :>> attestedCoordinatedReleases = false;
        attribute :>> attestedWorkflowsHardened = false;
    }
    satisfy requirement 'Open-MBEE/airflow-provider-opensysml: archived' : Policies::ArchiveNotice::Archived by 'Open-MBEE/airflow-provider-opensysml';
    satisfy requirement 'Open-MBEE/airflow-provider-opensysml: end-of-support-note' : Policies::ArchiveNotice::EndOfSupportNote by 'Open-MBEE/airflow-provider-opensysml';
    satisfy requirement 'Open-MBEE/airflow-provider-opensysml: review-required' : Policies::ChangeReview::ReviewRequired by 'Open-MBEE/airflow-provider-opensysml';
    satisfy requirement 'Open-MBEE/airflow-provider-opensysml: checks-required' : Policies::ChangeReview::ChecksRequired by 'Open-MBEE/airflow-provider-opensysml';
    satisfy requirement 'Open-MBEE/airflow-provider-opensysml: codeowners-present' : Policies::Codeowners::CodeownersPresent by 'Open-MBEE/airflow-provider-opensysml';
    satisfy requirement 'Open-MBEE/airflow-provider-opensysml: codeowners-valid' : Policies::Codeowners::CodeownersValid by 'Open-MBEE/airflow-provider-opensysml';
    satisfy requirement 'Open-MBEE/airflow-provider-opensysml: contributing-present' : Policies::Contributing::ContributingPresent by 'Open-MBEE/airflow-provider-opensysml';
    satisfy requirement 'Open-MBEE/airflow-provider-opensysml: contributing-content' : Policies::Contributing::ContributingContent by 'Open-MBEE/airflow-provider-opensysml';
    satisfy requirement 'Open-MBEE/airflow-provider-opensysml: dependabot-alerts-on' : Policies::DependencyManagement::DependabotAlertsOn by 'Open-MBEE/airflow-provider-opensysml';
    satisfy requirement 'Open-MBEE/airflow-provider-opensysml: dependency-policy' : Policies::DependencyManagement::DependencyPolicy by 'Open-MBEE/airflow-provider-opensysml';
    satisfy requirement 'Open-MBEE/airflow-provider-opensysml: service-pins' : Policies::DependencyManagement::ServicePins by 'Open-MBEE/airflow-provider-opensysml';
    satisfy requirement 'Open-MBEE/airflow-provider-opensysml: no-force-push' : Policies::HistoryProtection::NoForcePush by 'Open-MBEE/airflow-provider-opensysml';
    satisfy requirement 'Open-MBEE/airflow-provider-opensysml: no-deletion' : Policies::HistoryProtection::NoDeletion by 'Open-MBEE/airflow-provider-opensysml';
    satisfy requirement 'Open-MBEE/airflow-provider-opensysml: license-allowed' : Policies::LicenseByType::LicenseAllowed by 'Open-MBEE/airflow-provider-opensysml';
    satisfy requirement 'Open-MBEE/airflow-provider-opensysml: readme-present' : Policies::ProjectFiles::ReadmePresent by 'Open-MBEE/airflow-provider-opensysml';
    satisfy requirement 'Open-MBEE/airflow-provider-opensysml: sbom-attached' : Policies::ReleaseIntegrity::SbomAttached by 'Open-MBEE/airflow-provider-opensysml';
    satisfy requirement 'Open-MBEE/airflow-provider-opensysml: release-immutable' : Policies::ReleaseIntegrity::ReleaseImmutable by 'Open-MBEE/airflow-provider-opensysml';
    satisfy requirement 'Open-MBEE/airflow-provider-opensysml: signed-with-provenance' : Policies::ReleaseIntegrity::SignedWithProvenance by 'Open-MBEE/airflow-provider-opensysml';
    satisfy requirement 'Open-MBEE/airflow-provider-opensysml: no-built-executables' : Policies::ReleaseIntegrity::NoBuiltExecutables by 'Open-MBEE/airflow-provider-opensysml';
    satisfy requirement 'Open-MBEE/airflow-provider-opensysml: push-protection-on' : Policies::SecretProtection::PushProtectionOn by 'Open-MBEE/airflow-provider-opensysml';
    satisfy requirement 'Open-MBEE/airflow-provider-opensysml: design-current' : Policies::SecurityDesign::DesignCurrent by 'Open-MBEE/airflow-provider-opensysml';
    satisfy requirement 'Open-MBEE/airflow-provider-opensysml: security-policy-present' : Policies::SecurityPolicy::SecurityPolicyPresent by 'Open-MBEE/airflow-provider-opensysml';
    satisfy requirement 'Open-MBEE/airflow-provider-opensysml: private-reporting-on' : Policies::SecurityPolicy::PrivateReportingOn by 'Open-MBEE/airflow-provider-opensysml';
    satisfy requirement 'Open-MBEE/airflow-provider-opensysml: disclosure-followed' : Policies::SecurityPolicy::DisclosureFollowed by 'Open-MBEE/airflow-provider-opensysml';
    satisfy requirement 'Open-MBEE/airflow-provider-opensysml: semver-tags' : Policies::SemanticVersioning::SemverTags by 'Open-MBEE/airflow-provider-opensysml';
    satisfy requirement 'Open-MBEE/airflow-provider-opensysml: stable-release-policy' : Policies::SemanticVersioning::StableReleasePolicy by 'Open-MBEE/airflow-provider-opensysml';
    satisfy requirement 'Open-MBEE/airflow-provider-opensysml: code-scanning-configured' : Policies::StaticAnalysis::CodeScanningConfigured by 'Open-MBEE/airflow-provider-opensysml';
    satisfy requirement 'Open-MBEE/airflow-provider-opensysml: no-open-critical' : Policies::StaticAnalysis::NoOpenCritical by 'Open-MBEE/airflow-provider-opensysml';
    satisfy requirement 'Open-MBEE/airflow-provider-opensysml: verified-owners' : Policies::VerifiedCodeOwners::VerifiedOwners by 'Open-MBEE/airflow-provider-opensysml';
    satisfy requirement 'Open-MBEE/airflow-provider-opensysml: dependency-alerts-on-time' : Policies::VulnerabilityRemediation::DependencyAlertsOnTime by 'Open-MBEE/airflow-provider-opensysml';
    satisfy requirement 'Open-MBEE/airflow-provider-opensysml: scanning-clean' : Policies::VulnerabilityRemediation::ScanningClean by 'Open-MBEE/airflow-provider-opensysml';
    satisfy requirement 'Open-MBEE/airflow-provider-opensysml: coordinated-releases' : Policies::VulnerabilityRemediation::CoordinatedReleases by 'Open-MBEE/airflow-provider-opensysml';
    satisfy requirement 'Open-MBEE/airflow-provider-opensysml: default-token-read' : Policies::WorkflowLeastPrivilege::DefaultTokenRead by 'Open-MBEE/airflow-provider-opensysml';
    satisfy requirement 'Open-MBEE/airflow-provider-opensysml: workflows-hardened' : Policies::WorkflowLeastPrivilege::WorkflowsHardened by 'Open-MBEE/airflow-provider-opensysml';

    part 'Open-MBEE/sysml-toolkit' : Repository {
        attribute :>> type = Type::tool;
        attribute :>> stage = Stage::sandbox;
        attribute :>> attestedEndOfSupportNote = false;
        attribute :>> attestedContributingContent = false;
        attribute :>> attestedDependencyPolicy = false;
        attribute :>> attestedServicePins = false;
        attribute :>> attestedSignedWithProvenance = false;
        attribute :>> attestedNoBuiltExecutables = false;
        attribute :>> attestedDesignCurrent = false;
        attribute :>> attestedDisclosureFollowed = false;
        attribute :>> attestedStableReleasePolicy = false;
        attribute :>> attestedCoordinatedReleases = false;
        attribute :>> attestedWorkflowsHardened = false;
    }
    satisfy requirement 'Open-MBEE/sysml-toolkit: archived' : Policies::ArchiveNotice::Archived by 'Open-MBEE/sysml-toolkit';
    satisfy requirement 'Open-MBEE/sysml-toolkit: end-of-support-note' : Policies::ArchiveNotice::EndOfSupportNote by 'Open-MBEE/sysml-toolkit';
    satisfy requirement 'Open-MBEE/sysml-toolkit: review-required' : Policies::ChangeReview::ReviewRequired by 'Open-MBEE/sysml-toolkit';
    satisfy requirement 'Open-MBEE/sysml-toolkit: checks-required' : Policies::ChangeReview::ChecksRequired by 'Open-MBEE/sysml-toolkit';
    satisfy requirement 'Open-MBEE/sysml-toolkit: codeowners-present' : Policies::Codeowners::CodeownersPresent by 'Open-MBEE/sysml-toolkit';
    satisfy requirement 'Open-MBEE/sysml-toolkit: codeowners-valid' : Policies::Codeowners::CodeownersValid by 'Open-MBEE/sysml-toolkit';
    satisfy requirement 'Open-MBEE/sysml-toolkit: contributing-present' : Policies::Contributing::ContributingPresent by 'Open-MBEE/sysml-toolkit';
    satisfy requirement 'Open-MBEE/sysml-toolkit: contributing-content' : Policies::Contributing::ContributingContent by 'Open-MBEE/sysml-toolkit';
    satisfy requirement 'Open-MBEE/sysml-toolkit: dependabot-alerts-on' : Policies::DependencyManagement::DependabotAlertsOn by 'Open-MBEE/sysml-toolkit';
    satisfy requirement 'Open-MBEE/sysml-toolkit: dependency-policy' : Policies::DependencyManagement::DependencyPolicy by 'Open-MBEE/sysml-toolkit';
    satisfy requirement 'Open-MBEE/sysml-toolkit: service-pins' : Policies::DependencyManagement::ServicePins by 'Open-MBEE/sysml-toolkit';
    satisfy requirement 'Open-MBEE/sysml-toolkit: no-force-push' : Policies::HistoryProtection::NoForcePush by 'Open-MBEE/sysml-toolkit';
    satisfy requirement 'Open-MBEE/sysml-toolkit: no-deletion' : Policies::HistoryProtection::NoDeletion by 'Open-MBEE/sysml-toolkit';
    satisfy requirement 'Open-MBEE/sysml-toolkit: license-allowed' : Policies::LicenseByType::LicenseAllowed by 'Open-MBEE/sysml-toolkit';
    satisfy requirement 'Open-MBEE/sysml-toolkit: readme-present' : Policies::ProjectFiles::ReadmePresent by 'Open-MBEE/sysml-toolkit';
    satisfy requirement 'Open-MBEE/sysml-toolkit: sbom-attached' : Policies::ReleaseIntegrity::SbomAttached by 'Open-MBEE/sysml-toolkit';
    satisfy requirement 'Open-MBEE/sysml-toolkit: release-immutable' : Policies::ReleaseIntegrity::ReleaseImmutable by 'Open-MBEE/sysml-toolkit';
    satisfy requirement 'Open-MBEE/sysml-toolkit: signed-with-provenance' : Policies::ReleaseIntegrity::SignedWithProvenance by 'Open-MBEE/sysml-toolkit';
    satisfy requirement 'Open-MBEE/sysml-toolkit: no-built-executables' : Policies::ReleaseIntegrity::NoBuiltExecutables by 'Open-MBEE/sysml-toolkit';
    satisfy requirement 'Open-MBEE/sysml-toolkit: push-protection-on' : Policies::SecretProtection::PushProtectionOn by 'Open-MBEE/sysml-toolkit';
    satisfy requirement 'Open-MBEE/sysml-toolkit: design-current' : Policies::SecurityDesign::DesignCurrent by 'Open-MBEE/sysml-toolkit';
    satisfy requirement 'Open-MBEE/sysml-toolkit: security-policy-present' : Policies::SecurityPolicy::SecurityPolicyPresent by 'Open-MBEE/sysml-toolkit';
    satisfy requirement 'Open-MBEE/sysml-toolkit: private-reporting-on' : Policies::SecurityPolicy::PrivateReportingOn by 'Open-MBEE/sysml-toolkit';
    satisfy requirement 'Open-MBEE/sysml-toolkit: disclosure-followed' : Policies::SecurityPolicy::DisclosureFollowed by 'Open-MBEE/sysml-toolkit';
    satisfy requirement 'Open-MBEE/sysml-toolkit: semver-tags' : Policies::SemanticVersioning::SemverTags by 'Open-MBEE/sysml-toolkit';
    satisfy requirement 'Open-MBEE/sysml-toolkit: stable-release-policy' : Policies::SemanticVersioning::StableReleasePolicy by 'Open-MBEE/sysml-toolkit';
    satisfy requirement 'Open-MBEE/sysml-toolkit: code-scanning-configured' : Policies::StaticAnalysis::CodeScanningConfigured by 'Open-MBEE/sysml-toolkit';
    satisfy requirement 'Open-MBEE/sysml-toolkit: no-open-critical' : Policies::StaticAnalysis::NoOpenCritical by 'Open-MBEE/sysml-toolkit';
    satisfy requirement 'Open-MBEE/sysml-toolkit: verified-owners' : Policies::VerifiedCodeOwners::VerifiedOwners by 'Open-MBEE/sysml-toolkit';
    satisfy requirement 'Open-MBEE/sysml-toolkit: dependency-alerts-on-time' : Policies::VulnerabilityRemediation::DependencyAlertsOnTime by 'Open-MBEE/sysml-toolkit';
    satisfy requirement 'Open-MBEE/sysml-toolkit: scanning-clean' : Policies::VulnerabilityRemediation::ScanningClean by 'Open-MBEE/sysml-toolkit';
    satisfy requirement 'Open-MBEE/sysml-toolkit: coordinated-releases' : Policies::VulnerabilityRemediation::CoordinatedReleases by 'Open-MBEE/sysml-toolkit';
    satisfy requirement 'Open-MBEE/sysml-toolkit: default-token-read' : Policies::WorkflowLeastPrivilege::DefaultTokenRead by 'Open-MBEE/sysml-toolkit';
    satisfy requirement 'Open-MBEE/sysml-toolkit: workflows-hardened' : Policies::WorkflowLeastPrivilege::WorkflowsHardened by 'Open-MBEE/sysml-toolkit';

    part 'Open-MBEE/OpenSysML-FAQ' : Repository {
        attribute :>> type = Type::media;
        attribute :>> stage = Stage::incubating;
        attribute :>> attestedEndOfSupportNote = false;
        attribute :>> attestedContributingContent = false;
        attribute :>> attestedDependencyPolicy = false;
        attribute :>> attestedServicePins = false;
        attribute :>> attestedSignedWithProvenance = false;
        attribute :>> attestedNoBuiltExecutables = false;
        attribute :>> attestedDesignCurrent = false;
        attribute :>> attestedDisclosureFollowed = false;
        attribute :>> attestedStableReleasePolicy = false;
        attribute :>> attestedCoordinatedReleases = false;
        attribute :>> attestedWorkflowsHardened = false;
    }
    satisfy requirement 'Open-MBEE/OpenSysML-FAQ: archived' : Policies::ArchiveNotice::Archived by 'Open-MBEE/OpenSysML-FAQ';
    satisfy requirement 'Open-MBEE/OpenSysML-FAQ: end-of-support-note' : Policies::ArchiveNotice::EndOfSupportNote by 'Open-MBEE/OpenSysML-FAQ';
    satisfy requirement 'Open-MBEE/OpenSysML-FAQ: review-required' : Policies::ChangeReview::ReviewRequired by 'Open-MBEE/OpenSysML-FAQ';
    satisfy requirement 'Open-MBEE/OpenSysML-FAQ: checks-required' : Policies::ChangeReview::ChecksRequired by 'Open-MBEE/OpenSysML-FAQ';
    satisfy requirement 'Open-MBEE/OpenSysML-FAQ: codeowners-present' : Policies::Codeowners::CodeownersPresent by 'Open-MBEE/OpenSysML-FAQ';
    satisfy requirement 'Open-MBEE/OpenSysML-FAQ: codeowners-valid' : Policies::Codeowners::CodeownersValid by 'Open-MBEE/OpenSysML-FAQ';
    satisfy requirement 'Open-MBEE/OpenSysML-FAQ: contributing-present' : Policies::Contributing::ContributingPresent by 'Open-MBEE/OpenSysML-FAQ';
    satisfy requirement 'Open-MBEE/OpenSysML-FAQ: contributing-content' : Policies::Contributing::ContributingContent by 'Open-MBEE/OpenSysML-FAQ';
    satisfy requirement 'Open-MBEE/OpenSysML-FAQ: dependabot-alerts-on' : Policies::DependencyManagement::DependabotAlertsOn by 'Open-MBEE/OpenSysML-FAQ';
    satisfy requirement 'Open-MBEE/OpenSysML-FAQ: dependency-policy' : Policies::DependencyManagement::DependencyPolicy by 'Open-MBEE/OpenSysML-FAQ';
    satisfy requirement 'Open-MBEE/OpenSysML-FAQ: service-pins' : Policies::DependencyManagement::ServicePins by 'Open-MBEE/OpenSysML-FAQ';
    satisfy requirement 'Open-MBEE/OpenSysML-FAQ: no-force-push' : Policies::HistoryProtection::NoForcePush by 'Open-MBEE/OpenSysML-FAQ';
    satisfy requirement 'Open-MBEE/OpenSysML-FAQ: no-deletion' : Policies::HistoryProtection::NoDeletion by 'Open-MBEE/OpenSysML-FAQ';
    satisfy requirement 'Open-MBEE/OpenSysML-FAQ: license-allowed' : Policies::LicenseByType::LicenseAllowed by 'Open-MBEE/OpenSysML-FAQ';
    satisfy requirement 'Open-MBEE/OpenSysML-FAQ: readme-present' : Policies::ProjectFiles::ReadmePresent by 'Open-MBEE/OpenSysML-FAQ';
    satisfy requirement 'Open-MBEE/OpenSysML-FAQ: sbom-attached' : Policies::ReleaseIntegrity::SbomAttached by 'Open-MBEE/OpenSysML-FAQ';
    satisfy requirement 'Open-MBEE/OpenSysML-FAQ: release-immutable' : Policies::ReleaseIntegrity::ReleaseImmutable by 'Open-MBEE/OpenSysML-FAQ';
    satisfy requirement 'Open-MBEE/OpenSysML-FAQ: signed-with-provenance' : Policies::ReleaseIntegrity::SignedWithProvenance by 'Open-MBEE/OpenSysML-FAQ';
    satisfy requirement 'Open-MBEE/OpenSysML-FAQ: no-built-executables' : Policies::ReleaseIntegrity::NoBuiltExecutables by 'Open-MBEE/OpenSysML-FAQ';
    satisfy requirement 'Open-MBEE/OpenSysML-FAQ: push-protection-on' : Policies::SecretProtection::PushProtectionOn by 'Open-MBEE/OpenSysML-FAQ';
    satisfy requirement 'Open-MBEE/OpenSysML-FAQ: design-current' : Policies::SecurityDesign::DesignCurrent by 'Open-MBEE/OpenSysML-FAQ';
    satisfy requirement 'Open-MBEE/OpenSysML-FAQ: security-policy-present' : Policies::SecurityPolicy::SecurityPolicyPresent by 'Open-MBEE/OpenSysML-FAQ';
    satisfy requirement 'Open-MBEE/OpenSysML-FAQ: private-reporting-on' : Policies::SecurityPolicy::PrivateReportingOn by 'Open-MBEE/OpenSysML-FAQ';
    satisfy requirement 'Open-MBEE/OpenSysML-FAQ: disclosure-followed' : Policies::SecurityPolicy::DisclosureFollowed by 'Open-MBEE/OpenSysML-FAQ';
    satisfy requirement 'Open-MBEE/OpenSysML-FAQ: semver-tags' : Policies::SemanticVersioning::SemverTags by 'Open-MBEE/OpenSysML-FAQ';
    satisfy requirement 'Open-MBEE/OpenSysML-FAQ: stable-release-policy' : Policies::SemanticVersioning::StableReleasePolicy by 'Open-MBEE/OpenSysML-FAQ';
    satisfy requirement 'Open-MBEE/OpenSysML-FAQ: code-scanning-configured' : Policies::StaticAnalysis::CodeScanningConfigured by 'Open-MBEE/OpenSysML-FAQ';
    satisfy requirement 'Open-MBEE/OpenSysML-FAQ: no-open-critical' : Policies::StaticAnalysis::NoOpenCritical by 'Open-MBEE/OpenSysML-FAQ';
    satisfy requirement 'Open-MBEE/OpenSysML-FAQ: verified-owners' : Policies::VerifiedCodeOwners::VerifiedOwners by 'Open-MBEE/OpenSysML-FAQ';
    satisfy requirement 'Open-MBEE/OpenSysML-FAQ: dependency-alerts-on-time' : Policies::VulnerabilityRemediation::DependencyAlertsOnTime by 'Open-MBEE/OpenSysML-FAQ';
    satisfy requirement 'Open-MBEE/OpenSysML-FAQ: scanning-clean' : Policies::VulnerabilityRemediation::ScanningClean by 'Open-MBEE/OpenSysML-FAQ';
    satisfy requirement 'Open-MBEE/OpenSysML-FAQ: coordinated-releases' : Policies::VulnerabilityRemediation::CoordinatedReleases by 'Open-MBEE/OpenSysML-FAQ';
    satisfy requirement 'Open-MBEE/OpenSysML-FAQ: default-token-read' : Policies::WorkflowLeastPrivilege::DefaultTokenRead by 'Open-MBEE/OpenSysML-FAQ';
    satisfy requirement 'Open-MBEE/OpenSysML-FAQ: workflows-hardened' : Policies::WorkflowLeastPrivilege::WorkflowsHardened by 'Open-MBEE/OpenSysML-FAQ';

    part 'Open-MBEE/opensysml.github.io' : Repository {
        attribute :>> type = Type::media;
        attribute :>> stage = Stage::incubating;
        attribute :>> attestedEndOfSupportNote = false;
        attribute :>> attestedContributingContent = false;
        attribute :>> attestedDependencyPolicy = false;
        attribute :>> attestedServicePins = false;
        attribute :>> attestedSignedWithProvenance = false;
        attribute :>> attestedNoBuiltExecutables = false;
        attribute :>> attestedDesignCurrent = false;
        attribute :>> attestedDisclosureFollowed = false;
        attribute :>> attestedStableReleasePolicy = false;
        attribute :>> attestedCoordinatedReleases = false;
        attribute :>> attestedWorkflowsHardened = false;
    }
    satisfy requirement 'Open-MBEE/opensysml.github.io: archived' : Policies::ArchiveNotice::Archived by 'Open-MBEE/opensysml.github.io';
    satisfy requirement 'Open-MBEE/opensysml.github.io: end-of-support-note' : Policies::ArchiveNotice::EndOfSupportNote by 'Open-MBEE/opensysml.github.io';
    satisfy requirement 'Open-MBEE/opensysml.github.io: review-required' : Policies::ChangeReview::ReviewRequired by 'Open-MBEE/opensysml.github.io';
    satisfy requirement 'Open-MBEE/opensysml.github.io: checks-required' : Policies::ChangeReview::ChecksRequired by 'Open-MBEE/opensysml.github.io';
    satisfy requirement 'Open-MBEE/opensysml.github.io: codeowners-present' : Policies::Codeowners::CodeownersPresent by 'Open-MBEE/opensysml.github.io';
    satisfy requirement 'Open-MBEE/opensysml.github.io: codeowners-valid' : Policies::Codeowners::CodeownersValid by 'Open-MBEE/opensysml.github.io';
    satisfy requirement 'Open-MBEE/opensysml.github.io: contributing-present' : Policies::Contributing::ContributingPresent by 'Open-MBEE/opensysml.github.io';
    satisfy requirement 'Open-MBEE/opensysml.github.io: contributing-content' : Policies::Contributing::ContributingContent by 'Open-MBEE/opensysml.github.io';
    satisfy requirement 'Open-MBEE/opensysml.github.io: dependabot-alerts-on' : Policies::DependencyManagement::DependabotAlertsOn by 'Open-MBEE/opensysml.github.io';
    satisfy requirement 'Open-MBEE/opensysml.github.io: dependency-policy' : Policies::DependencyManagement::DependencyPolicy by 'Open-MBEE/opensysml.github.io';
    satisfy requirement 'Open-MBEE/opensysml.github.io: service-pins' : Policies::DependencyManagement::ServicePins by 'Open-MBEE/opensysml.github.io';
    satisfy requirement 'Open-MBEE/opensysml.github.io: no-force-push' : Policies::HistoryProtection::NoForcePush by 'Open-MBEE/opensysml.github.io';
    satisfy requirement 'Open-MBEE/opensysml.github.io: no-deletion' : Policies::HistoryProtection::NoDeletion by 'Open-MBEE/opensysml.github.io';
    satisfy requirement 'Open-MBEE/opensysml.github.io: license-allowed' : Policies::LicenseByType::LicenseAllowed by 'Open-MBEE/opensysml.github.io';
    satisfy requirement 'Open-MBEE/opensysml.github.io: readme-present' : Policies::ProjectFiles::ReadmePresent by 'Open-MBEE/opensysml.github.io';
    satisfy requirement 'Open-MBEE/opensysml.github.io: sbom-attached' : Policies::ReleaseIntegrity::SbomAttached by 'Open-MBEE/opensysml.github.io';
    satisfy requirement 'Open-MBEE/opensysml.github.io: release-immutable' : Policies::ReleaseIntegrity::ReleaseImmutable by 'Open-MBEE/opensysml.github.io';
    satisfy requirement 'Open-MBEE/opensysml.github.io: signed-with-provenance' : Policies::ReleaseIntegrity::SignedWithProvenance by 'Open-MBEE/opensysml.github.io';
    satisfy requirement 'Open-MBEE/opensysml.github.io: no-built-executables' : Policies::ReleaseIntegrity::NoBuiltExecutables by 'Open-MBEE/opensysml.github.io';
    satisfy requirement 'Open-MBEE/opensysml.github.io: push-protection-on' : Policies::SecretProtection::PushProtectionOn by 'Open-MBEE/opensysml.github.io';
    satisfy requirement 'Open-MBEE/opensysml.github.io: design-current' : Policies::SecurityDesign::DesignCurrent by 'Open-MBEE/opensysml.github.io';
    satisfy requirement 'Open-MBEE/opensysml.github.io: security-policy-present' : Policies::SecurityPolicy::SecurityPolicyPresent by 'Open-MBEE/opensysml.github.io';
    satisfy requirement 'Open-MBEE/opensysml.github.io: private-reporting-on' : Policies::SecurityPolicy::PrivateReportingOn by 'Open-MBEE/opensysml.github.io';
    satisfy requirement 'Open-MBEE/opensysml.github.io: disclosure-followed' : Policies::SecurityPolicy::DisclosureFollowed by 'Open-MBEE/opensysml.github.io';
    satisfy requirement 'Open-MBEE/opensysml.github.io: semver-tags' : Policies::SemanticVersioning::SemverTags by 'Open-MBEE/opensysml.github.io';
    satisfy requirement 'Open-MBEE/opensysml.github.io: stable-release-policy' : Policies::SemanticVersioning::StableReleasePolicy by 'Open-MBEE/opensysml.github.io';
    satisfy requirement 'Open-MBEE/opensysml.github.io: code-scanning-configured' : Policies::StaticAnalysis::CodeScanningConfigured by 'Open-MBEE/opensysml.github.io';
    satisfy requirement 'Open-MBEE/opensysml.github.io: no-open-critical' : Policies::StaticAnalysis::NoOpenCritical by 'Open-MBEE/opensysml.github.io';
    satisfy requirement 'Open-MBEE/opensysml.github.io: verified-owners' : Policies::VerifiedCodeOwners::VerifiedOwners by 'Open-MBEE/opensysml.github.io';
    satisfy requirement 'Open-MBEE/opensysml.github.io: dependency-alerts-on-time' : Policies::VulnerabilityRemediation::DependencyAlertsOnTime by 'Open-MBEE/opensysml.github.io';
    satisfy requirement 'Open-MBEE/opensysml.github.io: scanning-clean' : Policies::VulnerabilityRemediation::ScanningClean by 'Open-MBEE/opensysml.github.io';
    satisfy requirement 'Open-MBEE/opensysml.github.io: coordinated-releases' : Policies::VulnerabilityRemediation::CoordinatedReleases by 'Open-MBEE/opensysml.github.io';
    satisfy requirement 'Open-MBEE/opensysml.github.io: default-token-read' : Policies::WorkflowLeastPrivilege::DefaultTokenRead by 'Open-MBEE/opensysml.github.io';
    satisfy requirement 'Open-MBEE/opensysml.github.io: workflows-hardened' : Policies::WorkflowLeastPrivilege::WorkflowsHardened by 'Open-MBEE/opensysml.github.io';

    part 'Open-MBEE/governance-checks' : Repository {
        attribute :>> type = Type::tool;
        attribute :>> stage = Stage::incubating;
        attribute :>> attestedEndOfSupportNote = false;
        attribute :>> attestedContributingContent = false;
        attribute :>> attestedDependencyPolicy = false;
        attribute :>> attestedServicePins = false;
        attribute :>> attestedSignedWithProvenance = false;
        attribute :>> attestedNoBuiltExecutables = false;
        attribute :>> attestedDesignCurrent = false;
        attribute :>> attestedDisclosureFollowed = false;
        attribute :>> attestedStableReleasePolicy = false;
        attribute :>> attestedCoordinatedReleases = false;
        attribute :>> attestedWorkflowsHardened = false;
    }
    satisfy requirement 'Open-MBEE/governance-checks: archived' : Policies::ArchiveNotice::Archived by 'Open-MBEE/governance-checks';
    satisfy requirement 'Open-MBEE/governance-checks: end-of-support-note' : Policies::ArchiveNotice::EndOfSupportNote by 'Open-MBEE/governance-checks';
    satisfy requirement 'Open-MBEE/governance-checks: review-required' : Policies::ChangeReview::ReviewRequired by 'Open-MBEE/governance-checks';
    satisfy requirement 'Open-MBEE/governance-checks: checks-required' : Policies::ChangeReview::ChecksRequired by 'Open-MBEE/governance-checks';
    satisfy requirement 'Open-MBEE/governance-checks: codeowners-present' : Policies::Codeowners::CodeownersPresent by 'Open-MBEE/governance-checks';
    satisfy requirement 'Open-MBEE/governance-checks: codeowners-valid' : Policies::Codeowners::CodeownersValid by 'Open-MBEE/governance-checks';
    satisfy requirement 'Open-MBEE/governance-checks: contributing-present' : Policies::Contributing::ContributingPresent by 'Open-MBEE/governance-checks';
    satisfy requirement 'Open-MBEE/governance-checks: contributing-content' : Policies::Contributing::ContributingContent by 'Open-MBEE/governance-checks';
    satisfy requirement 'Open-MBEE/governance-checks: dependabot-alerts-on' : Policies::DependencyManagement::DependabotAlertsOn by 'Open-MBEE/governance-checks';
    satisfy requirement 'Open-MBEE/governance-checks: dependency-policy' : Policies::DependencyManagement::DependencyPolicy by 'Open-MBEE/governance-checks';
    satisfy requirement 'Open-MBEE/governance-checks: service-pins' : Policies::DependencyManagement::ServicePins by 'Open-MBEE/governance-checks';
    satisfy requirement 'Open-MBEE/governance-checks: no-force-push' : Policies::HistoryProtection::NoForcePush by 'Open-MBEE/governance-checks';
    satisfy requirement 'Open-MBEE/governance-checks: no-deletion' : Policies::HistoryProtection::NoDeletion by 'Open-MBEE/governance-checks';
    satisfy requirement 'Open-MBEE/governance-checks: license-allowed' : Policies::LicenseByType::LicenseAllowed by 'Open-MBEE/governance-checks';
    satisfy requirement 'Open-MBEE/governance-checks: readme-present' : Policies::ProjectFiles::ReadmePresent by 'Open-MBEE/governance-checks';
    satisfy requirement 'Open-MBEE/governance-checks: sbom-attached' : Policies::ReleaseIntegrity::SbomAttached by 'Open-MBEE/governance-checks';
    satisfy requirement 'Open-MBEE/governance-checks: release-immutable' : Policies::ReleaseIntegrity::ReleaseImmutable by 'Open-MBEE/governance-checks';
    satisfy requirement 'Open-MBEE/governance-checks: signed-with-provenance' : Policies::ReleaseIntegrity::SignedWithProvenance by 'Open-MBEE/governance-checks';
    satisfy requirement 'Open-MBEE/governance-checks: no-built-executables' : Policies::ReleaseIntegrity::NoBuiltExecutables by 'Open-MBEE/governance-checks';
    satisfy requirement 'Open-MBEE/governance-checks: push-protection-on' : Policies::SecretProtection::PushProtectionOn by 'Open-MBEE/governance-checks';
    satisfy requirement 'Open-MBEE/governance-checks: design-current' : Policies::SecurityDesign::DesignCurrent by 'Open-MBEE/governance-checks';
    satisfy requirement 'Open-MBEE/governance-checks: security-policy-present' : Policies::SecurityPolicy::SecurityPolicyPresent by 'Open-MBEE/governance-checks';
    satisfy requirement 'Open-MBEE/governance-checks: private-reporting-on' : Policies::SecurityPolicy::PrivateReportingOn by 'Open-MBEE/governance-checks';
    satisfy requirement 'Open-MBEE/governance-checks: disclosure-followed' : Policies::SecurityPolicy::DisclosureFollowed by 'Open-MBEE/governance-checks';
    satisfy requirement 'Open-MBEE/governance-checks: semver-tags' : Policies::SemanticVersioning::SemverTags by 'Open-MBEE/governance-checks';
    satisfy requirement 'Open-MBEE/governance-checks: stable-release-policy' : Policies::SemanticVersioning::StableReleasePolicy by 'Open-MBEE/governance-checks';
    satisfy requirement 'Open-MBEE/governance-checks: code-scanning-configured' : Policies::StaticAnalysis::CodeScanningConfigured by 'Open-MBEE/governance-checks';
    satisfy requirement 'Open-MBEE/governance-checks: no-open-critical' : Policies::StaticAnalysis::NoOpenCritical by 'Open-MBEE/governance-checks';
    satisfy requirement 'Open-MBEE/governance-checks: verified-owners' : Policies::VerifiedCodeOwners::VerifiedOwners by 'Open-MBEE/governance-checks';
    satisfy requirement 'Open-MBEE/governance-checks: dependency-alerts-on-time' : Policies::VulnerabilityRemediation::DependencyAlertsOnTime by 'Open-MBEE/governance-checks';
    satisfy requirement 'Open-MBEE/governance-checks: scanning-clean' : Policies::VulnerabilityRemediation::ScanningClean by 'Open-MBEE/governance-checks';
    satisfy requirement 'Open-MBEE/governance-checks: coordinated-releases' : Policies::VulnerabilityRemediation::CoordinatedReleases by 'Open-MBEE/governance-checks';
    satisfy requirement 'Open-MBEE/governance-checks: default-token-read' : Policies::WorkflowLeastPrivilege::DefaultTokenRead by 'Open-MBEE/governance-checks';
    satisfy requirement 'Open-MBEE/governance-checks: workflows-hardened' : Policies::WorkflowLeastPrivilege::WorkflowsHardened by 'Open-MBEE/governance-checks';

}
